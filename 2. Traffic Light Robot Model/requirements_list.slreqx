# requirements_list

## TrafficLightStatusCounter: سیستم برای کنترل زمان تغییر وضعیت چراغ‌ها از شمارنده مخصوص چراغ ترافیکی استفاده می‌کند. (Functional)

## TrafficLightSequence: چراغ راهنمایی به ترتیب از قرمز به سبز و سپس به زرد تغییر می‌کند. (Functional)

## PedestrianCrossingCondition: سیستم تنها زمانی اجازه عبور به عابر می‌دهد که حداقل ۵۵ واحد زمانی از آخرین عبور گذشته باشد. (Functional)

## GreenLightReturn: پس از پایان زمان عبور عابر، سیستم دوباره به چراغ سبز برای خودروها بازمی‌گردد. (Functional)

## PedestrianButtonGreenToYellow: زمانی که دکمه عبور عابر پیاده فشرده می‌شود و چراغ راهنمایی در حالت سبز است، پس از گذشت زمان کافی چراغ به حالت زرد تغییر می‌کند. (Functional)

## PedestrianWaitTimer: شمارنده‌ای مختص به عابر پیاده نیز برای اندازه‌گیری مدت انتظار عابر پیاده استفاده می‌شود. (Functional)

## EarlyPedestrianButtonPress: اگر دکمه عبور خیلی زود زده شود، درخواست تا زمان مناسب منتظر می‌ماند و بلافاصله اجرا نمی‌شود. (Functional)

## LightStatusReset: با هر بار تغییر وضعیت چراغ، مقادیر زمان‌ها ریست یا به‌روزرسانی می‌شوند. (Functional)

## PedestrianGreenLightAccess: در زمان روشن بودن چراغ سبز عابر، عابران اجازه عبور از خیابان را دارند. (Functional)

## RedToGreenTransition: بعد از چراغ زرد، چراغ راهنمایی به رنگ قرمز درمی‌آید و چراغ عبور عابر به رنگ سبز تغییر می‌کند. (Functional)

## NoSimultaneousGreenLights: نباید همزمان چراغ عابر و چراغ راهنمایی و رانندگی سبز باشند. (Functional)

## SystemReliabilityRequirement: قابلیت اطمینان سیستم باید 99.9 درصد مواقع به‌درستی عمل کند تا ایمنی در تقاطع‌ها تضمین شود. این الزام به مدل‌های Simulink برای تشخیص خطا و مکانیزم‌های افزونگی لینک می‌شود. (Informational)
برای آزمون، سیستم باید به مدت 1000 ساعت اجرا شده و تأیید شود که زمان خرابی کمتر از 0.1 درصد (یعنی کمتر از 1 ساعت) است. هدف قابلیت اطمینان (99.9 درصد) به‌وضوح مشخص است و باید تعریف دقیقی از «عملکرد صحیح» ارائه شود، مانند عملکرد بدون چراغ‌های نادرست. الزام بدون تعارض و برای ایمنی سیستم حیاتی است.

## SafeFailureMechanism: ایمنی (مکانیزم ایمن در برابر خرابی) در صورت قطع برق یا خرابی سخت‌افزاری، سیستم باید به حالت ایمن برود. در صورت قطع برق یا خرابی سخت‌افزاری، سیستم باید به حالت ایمن برود؛ برای مثال، همه چراغ‌ها باید به قرمز چشمک‌زن تغییر وضعیت دهند. (Informational)
این الزام به بلوک‌های Simulink برای تشخیص خرابی و منطق ایمن مرتبط است. با شبیه‌سازی قطع برق، تأیید می‌شود که همه چراغ‌ها در کمتر از 1 ثانیه به وضعیت ایمن تغییر می‌کنند. در مورد رفتار ایمن شفافیت کامل وجود دارد، و فرکانس چشمک‌زدن (مثلاً 1 هرتز) و مدت زمان آن (مثلاً تا بازگشت برق) باید مشخص گردد. این الزام با استانداردهای ایمنی همچون ISO 26262 سازگار است.

## EnvironmentalResistance: سیستم باید در برابر شرایط محیطی سخت مانند باران، برف و گرمای شدید مقاوم باشد و حداقل 10 سال عمر مفید داشته باشد. این الزام به طراحی سخت‌افزاری، انتخاب مواد و آزمایش‌های فیزیکی مرتبط است. (Informational)
برای آزمون، سیستم در معرض دماهای -20 تا 50 درجه سانتی‌گراد و رطوبت 95 درصد قرار گرفته و عملکرد آن در شرایط شبیه‌سازی‌شده 10 ساله بررسی می‌شود. اطلاعات در مورد عمر مفید و شرایط محیطی به‌وضوح ارائه شده‌اند و باید استانداردهایی مانند IP65 برای مقاومت در برابر آب مشخص شوند. این الزام با اهداف قابلیت اطمینان بلندمدت سازگار است.

## VisibilityDistance: چراغ‌ها باید از فاصله حداقل 100 متری در نور روز و شرایط آب‌وهوایی نامساعد (مانند مه یا باران شدید) دیده شوند. این الزام به مدل‌های Simulink برای کنترل شدت نور و طراحی سخت‌افزاری LED لینک می‌شود. (Informational)
در آزمون، فاصله دید در شرایط کنترل‌شده سنجیده می‌شود تا تأیید گردد که حداقل 100 متر است. اطلاعات در مورد فاصله و شرایط مشاهده به‌وضوح بیان شده و باید شدت نور (مثلاً 500 کاندلا) و رنگ‌های استاندارد ترافیکی مشخص شود. این الزام با الزامات ایمنی و قابلیت استفاده هم‌خوانی دارد.

## SignalChangeTime: سیستم باید سیگنال‌ها را در کمتر از 1 ثانیه پس از وقوع محرک‌هایی مانند انقضای تایمر یا دریافت ورودی از حسگر تغییر دهد. این الزام به منطق زمان‌بندی و بلوک‌های تغییر سیگنال در Simulink مرتبط است. (Informational)
آزمون شامل ایجاد یک محرک و اندازه‌گیری زمان تغییر سیگنال است تا تأیید شود که کمتر از 1 ثانیه است. شفافیت در مورد زمان پاسخگویی و محرک وجود دارد و می‌توان هدف دقیق‌تری مانند 0.5 ثانیه نیز تعیین کرد. این الزام بدون تعارض بوده و از عملکرد بلادرنگ سیستم پشتیبانی می‌کند.

## EnergyEfficiency: بهره‌وری انرژی: سیستم باید در محدوده مصرف انرژی 500 وات عمل کند تا هزینه‌های انرژی کاهش یابد. این الزام به مدل‌های Simulink برای مدیریت انرژی و طراحی سخت‌افزاری برای بهینه‌سازی LEDها مرتبط است. (Informational)
آزمون شامل اندازه‌گیری مصرف انرژی در حالت عادی سیستم است و باید تأیید گردد که کمتر از 500 وات است. در مورد میزان مصرف و شرایط عملیاتی شفافیت وجود دارد، و باید اطلاعاتی مانند منبع تغذیه (مثلاً برق شبکه) و وضعیت کامل بار (مثلاً تمام چراغ‌ها روشن) مشخص گردد. این الزام با اهداف پایداری سازگار است.

## TechnicianMaintenance: سیستم باید به تکنسین‌ها اجازه دهد تا تعمیرات یا به‌روزرسانی‌ها را در کمتر از 2 ساعت انجام دهند، بدون اینکه اختلال چشمگیری در ترافیک ایجاد شود. (Informational)
این الزام به مدل‌های Simulink برای تشخیص خطا و طراحی سخت‌افزاری برای دسترسی آسان به اجزای سیستم لینک می‌شود. آزمون شامل شبیه‌سازی یک عملیات تعمیراتی مانند تعویض ماژول چراغ است و زمان انجام آن اندازه‌گیری می‌شود. اطلاعات در مورد محدودیت زمانی و حداقل‌سازی اختلال ترافیکی شفاف است، و باید مشخص شود تعمیرات شامل چه مواردی می‌شود و سطح اختلال قابل‌قبول چقدر است (مثلاً کمتر از 10 دقیقه). این الزام با نیازهای عملیاتی سیستم سازگار است.
