# aircraft_reqs

## R-1: Aircraft moves at constant speed of 1km/h along axes. (Functional)

## R-2: Heading changes only in ±90° steps at decision ticks; no 180° reversal. (Functional)

## R-3: Never allow another aircraft into your “danger” square. (Functional)

## R-4: Use comms only when the other aircraft is inside the “communication” square. (Functional)

## R-5: Reach destination (time-optimal subject to R-3/R-4). (Functional)

## R-6: Provide 2D plots of flown paths; deliver coverage & test evidence. (Functional)
